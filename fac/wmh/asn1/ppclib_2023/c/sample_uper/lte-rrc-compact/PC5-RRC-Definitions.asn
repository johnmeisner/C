-- This file was generated by the Objective Systems ASN1C Compiler
-- (http://www.obj-sys.com).  Version: 7.6.2.3, Date: 17-Oct-2022.

PC5-RRC-Definitions DEFINITIONS AUTOMATIC TAGS ::= BEGIN

IMPORTS

TDD-ConfigSL-r12
FROM EUTRA-RRC-Definitions ;

-- Productions

MasterInformationBlock-SL ::= SEQUENCE {
   sl-Bandwidth-r12 [0] ENUMERATED { n6(0), n15(1), n25(2), n50(3), n75(4), 
      n100(5) },
   tdd-ConfigSL-r12 [1] TDD-ConfigSL-r12,
   directFrameNumber-r12 [2] BIT STRING  (SIZE (10)),
   directSubframeNumber-r12 [3] INTEGER (0..9),
   inCoverage-r12 [4] BOOLEAN,
   reserved-r12 [5] BIT STRING  (SIZE (19))
}

SBCCH-SL-BCH-MessageType ::= MasterInformationBlock-SL

MasterInformationBlock-SL-V2X-r14 ::= SEQUENCE {
   sl-Bandwidth-r14 [0] ENUMERATED { n6(0), n15(1), n25(2), n50(3), n75(4), 
      n100(5) },
   tdd-ConfigSL-r14 [1] TDD-ConfigSL-r12,
   directFrameNumber-r14 [2] BIT STRING  (SIZE (10)),
   directSubframeNumber-r14 [3] INTEGER (0..9),
   inCoverage-r14 [4] BOOLEAN,
   reserved-r14 [5] BIT STRING  (SIZE (27))
}

SBCCH-SL-BCH-MessageType-V2X-r14 ::= MasterInformationBlock-SL-V2X-r14

SBCCH-SL-BCH-Message ::= SEQUENCE {
   message [0] SBCCH-SL-BCH-MessageType
}

SBCCH-SL-BCH-Message-V2X-r14 ::= SEQUENCE {
   message [0] SBCCH-SL-BCH-MessageType-V2X-r14
}

END
